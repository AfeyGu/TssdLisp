(lib::lsp "TszLib")
(setfunhelp "c:CHCYSHTH" "Tssd" "CHCYSHTH")
(defun c:CHCYSHTH (/ e et le sl ss st #shdcl) 
  (Defun #shdcl (eo / el l1 ln nln rt tf) 
    (if (new_dialog "CHCYSHTH" (lib::dcl "TszDim")) 
      (progn (setq tf T) 
             (while (setq el (tblnext "Dimstyle" tf)) 
               (setq ln (cons (cdr (assoc 2 el)) ln)
                     tf nil
               )
             )
             (setq ln  (acad_strlsort ln)
                   l1  (member eo ln)
                   nln (if l1 (itoa (- (length ln) (length l1))) "0")
             )
             (set_tile "eo" eo)
             (Dcl::lbox "ln")
             (setq rt (start_dialog))
             (if (= rt 1) (nth (atoi nln) ln))
      )
    )
  )
  (lib::LspBeg)
  (if (setq ss (&DSTR "\n选择要替换样式的尺寸<退出>: " '((0 . "dimension")))) 
    (progn (setq sl (sslength ss)) 
           (while (> sl 0) 
             (setq sl (1- sl)
                   e  (ssname ss sl)
                   le (cons e le)
                   et (&DRAG e 3)
             )
             (if (null st) (setq st et))
             (if (/= st et) (setq st "*多种*"))
           )
           (if (setq st (#shdcl st)) 
             (foreach e le (lib::eupd e (list (list 3 st))))
           )
    )
  )
  (&TSTY)
)
(setfunhelp "c:WZYD" "Tssd" "WZYD")
(defun c:WZYD (/ e sl ss tf) 
  (lib::LspBeg)
  (setq tf t)
  (while 
    (and tf 
         (progn (initget "G") 
                (setq e (&DOVR "\n选取要移动文字的尺寸[文字归位(G)]<退出>: " '((0 . "dimension"))))
         )
    )
    (if (= "G" e) 
      (progn (setq tf nil) 
             (if (setq ss (&DSTR "\n选择要文字归位的尺寸<退出>:" '((0 . "dimension")))) 
               (progn (setq sl (sslength ss)) 
                      (while (> sl 0) 
                        (setq sl (1- sl)
                              e  (ssname ss sl)
                        )
                        (command ".dimtedit" e "c")
                      )
               )
             )
      )
      (progn (command ".dimtedit") 
             (setvar "cmdecho" 1)
             (command e)
             (while (/= (getvar "cmdactive") 0) (command pause))
             (setvar "cmdecho" 0)
      )
    )
  )
  (&TSTY)
)
(Defun dim:flt (l / i j l1) 
  (setq l1 '((0 . "dimension") (-4 . "<or")))
  (foreach i l 
    (setq l1 (append l1 (mapcar '(lambda (j) (cons 70 (+ i j))) '(0 32 128 160))))
  )
  (append l1 '((-4 . "or>")))
)
(Defun dim:align (ty / ss) 
  (lib::LspBeg)
  (if (setq ss (&DSTR "\n选择要对齐的尺寸<退出>: " (dim:flt '(0 1 5)))) 
    (progn (&DSTY ss ty) (&CODE ss))
  )
  (&TSTY)
)
(setfunhelp "c:wzhqq" "Tssd" "wzhqq")
(defun c:wzhqq () (dim:align 0))
(setfunhelp "c:Xchqq" "Tssd" "XCHQQ")
(defun c:Xchqq () (dim:align 1))
(setfunhelp "c:Kdqq" "Tssd" "KDQQ")
(defun c:Kdqq () (dim:align 2))
(setfunhelp "c:Wzfzh" "Tssd" "WZFZH")
(defun c:Wzfzh (/ a e si ss) 
  (lib::LspBeg)
  (if (setq ss (&DSTR "\n选取要翻转文字的尺寸<退出>: " '((0 . "dimension")))) 
    (progn (setq si -1) 
           (while 
             (setq si (1+ si)
                   e  (ssname ss si)
             )
             (setq a (&DRAG e 51)
                   a (if (and (>= pi a) (> a 0)) 0 pi)
             )
             (lib::eupd e (list (list 51 (lib::u2wcs a))))
           )
    )
  )
  (&TSTY)
)
(setfunhelp "c:Gchczh" "Tssd" "GCHCZH")
(defun c:Gchczh (/ ss val) 
  (lib::LspBeg)
  (if (setq ss (&DSTR "\n选择要修改标注值(或恢复原值)的尺寸<退出>: " '((0 . "dimension")))) 
    (progn (setq val (getstring "\n输入新的尺寸值<恢复原值>：")) 
           (command ".dim1" "new" val ss "")
    )
  )
  (&TSTY)
)
(setfunhelp "c:bzhhb" "Tssd" "bzhhb")
(defun c:bzhhb (/ ax1 ax2 c1 c2 d de ds e e70 l l1 ldm1 ldm2 le lfd ll mm mma mx p0 
                q1 q2 q3 q4 q5 si ss tf tf2 tfhb tfzf mkal hbdma
               ) 
  (defun mkal (tf23 q1 q3 q4 q5 q6 / ax0 ax1 ax2 l l1 ll r1 r2) 
    (setq c1 (if tfzf 14 10)
          c2 (if tfzf 13 15)
    )
    (if (not tf23) 
      (progn 
        (if (< (distance p0 q3) (distance p0 q5)) 
          (progn (&PMLAY "q3" "q5") 
                 (setq c1 (if tfzf 14 15)
                       c2 (if tfzf 13 10)
                 )
          )
        )
        (if (< (distance p0 q4) (distance p0 q6)) 
          (progn (&PMLAY "q4" "q6") 
                 (setq c1 (if tfzf 13 10)
                       c2 (if tfzf 14 15)
                 )
          )
        )
      )
    )
    (setq ax0  (angle p0 q1)
          ax1  (angle p0 q3)
          ax2  (angle p0 q4)
          r1   (distance p0 q1)
          r2   (distance p0 (&DRAG 11))
          ax0  (lib::upang ax0 ax1)
          ax2  (lib::upang ax2 ax1)
          tfzf (> ax2 ax0 ax1)
          ax2  (lib::atidy ax2 _2pi)
    )
    (if (null tfzf) (&PMLAY "ax1" "ax2"))
    (setq l1   (list p0 r1)
          ll   (lib::asso l1 ldm2 mm)
          q3   (if tfzf q3 q4)
          q5   (if tfzf q5 q6)
          l    (if (> ax1 ax2) 
                 (list (list ax1 _2pi tfzf tf23 q3 q5 r2 e) (list 0 ax2))
                 (list (list ax1 ax2 tfzf tf23 q3 q5 r2 e))
               )
          ldm2 (if ll (subst (append ll l) ll ldm2) (cons (cons l1 l) ldm2))
    )
  )
  (defun hbdma (/ ax ax1 e e1 el p1 p2 q r1 r2 rt tf23 tfzf x) 
    (if le 
      (progn (lib::lset '(ax1 x tfzf tf23 p1 p2 rt e) l) 
             (setq ax (- ax2 ax1)
                   ax (/ (if (< ax 0) (+ ax _2pi) ax) 2)
                   q  (polar p0 (+ ax1 ax) rt)
                   r1 (distance p0 p1)
                   p1 (polar p0 ax2 r1)
             )
             (if (not (and (null tf23) (> ax (- _pi2 mma)))) 
               (progn (foreach e1 le (entdel e1)) 
                      (if tf23 
                        (setq el (list (list 11 (lib::u2wcs q)) 
                                       (list (if tfzf 13 14) (lib::u2wcs p1))
                                 )
                        )
                        (setq r2 (distance p0 p2)
                              p2 (polar p0 ax2 r2)
                              el (list (list 11 (lib::u2wcs q)) 
                                       (list c1 (lib::u2wcs p1))
                                       (list c2 (lib::u2wcs p2))
                                 )
                        )
                      )
                      (lib::eupd e el)
               )
             )
      )
    )
  )
  (lib::LspBeg)
  (if (setq ss (&DSTR "\n选择要合并的尺寸<退出>: " (dim:flt '(0 1 2 5)))) 
    (progn 
      (setq mm  (lib::gpels 1)
            mx  1e5
            mma 1e-3
            si  -1
      )
      (while 
        (setq si (1+ si)
              e  (ssname ss si)
        )
        (setq q1 (&DRAG e 10)
              q4 (&DRAG 13)
              q3 (&DRAG 14)
              tf (rem (&DRAG 70) 32)
        )
        (cond 
          ((< tf 2)
           (setq ax1  (if (zerop tf) (&DRAG 50) (angle q4 q3))
                 ax2  (+ ax1 _pi2)
                 q5   (polar q1 ax2 mx)
                 q2   (inters q1 (polar q1 ax1 mx) q4 (polar q4 ax2 mx) nil)
                 ax1  (lib::atidy ax1 pi)
                 ll   (lib::asso ax1 ldm1 mma)
                 l    (list q1 q2 q3 q4 e)
                 ldm1 (if ll 
                        (subst (append ll (list l)) ll ldm1)
                        (cons (list ax1 l) ldm1)
                      )
           )
          )
          ((= tf 5) (setq p0 (&DRAG 15)) (mkal T q1 q3 q4 nil nil))
          ((= tf 2)
           (setq q2 (&DRAG 15)
                 q5 (&DRAG 16)
                 p0 (inters q1 q2 q3 q4 nil)
           )
           (if p0 (mkal nil q5 q1 q3 q2 q4))
          )
        )
      )
      (foreach ll ldm1 
        (setq ax1 (car ll)
              ax2 (+ ax1 _pi2)
              l   (cadr ll)
              q1  (car l)
              q2  (polar q1 ax1 mx)
              q3  (polar q1 ax2 mx)
              lfd nil
        )
        (foreach l (cdr ll) 
          (setq d    (&MIDP (car l) q1 q2)
                ds   (&MIDP (car l) q1 q3)
                de   (&MIDP (cadr l) q1 q3)
                tfzf (< ds de)
                l    (cons (if tfzf ds de) (cons (if tfzf de ds) (cons tfzf l)))
                l1   (lib::asso d lfd mm)
                lfd  (if l1 
                       (subst (append l1 (list l)) l1 lfd)
                       (cons (list d l) lfd)
                     )
          )
        )
        (foreach ll lfd 
          (setq ll  (lib::ran3 (cdr ll))
                tf2 (= 2 (length ll))
          )
          (while (setq l (car ll)) 
            (setq d    (cadr l)
                  tfhb nil
            )
            (while 
              (and 
                (setq ll (cdr ll)
                      l1 (car ll)
                )
                (or (> d (- (car l1) mm)) tf2)
              )
              (setq d    (cadr l1)
                    tfhb t
              )
              (entdel (last l1))
            )
            (if tfhb 
              (progn 
                (setq e70 (&DRAG (last l) 70)
                      d   (- d (car l))
                )
                (if (caddr l) 
                  (lib::eupd 
                    (last l)
                    (list (list 13 (lib::u2wcs (polar (nth 5 l) ax1 d))))
                  )
                  (lib::eupd 
                    (last l)
                    (list (list 14 (lib::u2wcs (polar (nth 6 l) ax1 d))))
                  )
                )
                (if (= 128 (logand 128 e70)) (command ".dim1" "hom" (last l) ""))
              )
            )
          )
        )
      )
      (foreach ll ldm2 
        (if (> (length ll) 2) 
          (progn 
            (setq l   (car ll)
                  p0  (car l)
                  ll  (lib::ran3 (cdr ll))
                  tf2 (= 2 (length ll))
            )
            (while (setq l (car ll)) 
              (setq ax2 (cadr l)
                    le  nil
              )
              (while 
                (and 
                  (setq ll (cdr ll)
                        l1 (car ll)
                  )
                  (or (> ax2 (- (car l1) mma)) tf2)
                )
                (setq ax2 (cadr l1)
                      e   (last l1)
                )
                (if (= 'ENAME (type e)) 
                  (setq le (cons e le))
                )
              )
              (cond 
                ((not ll))
                ((not (equal (car l) 0 mma))
                 (hbdma)
                )
                ((equal (cadr (last ll)) _2pi mma)
                 (setq ll (reverse ll)
                       l  (car ll)
                 )
                 (while 
                   (and 
                     (setq ll (cdr ll)
                           l1 (car ll)
                     )
                     (> (cadr l1) (- (car l) mm))
                   )
                   (setq e  (last l)
                         le (if (= 'ENAME (type e)) 
                              (cons e le)
                              le
                            )
                         l  l1
                   )
                 )
                 (setq ll (reverse ll))
                 (hbdma)
                )
                (T (hbdma))
              )
            )
          )
        )
      )
    )
  )
  (&TSTY )
)
(setfunhelp "c:Bzhdk" "Tssd" "BZHDK")
(Defun c:Bzhdk (/ a a1 a2 a3 ae as ax ax1 ax2 ay de ds dx e e1 e70 el i i1 i2 ie is l 
                l1 l2 le le1 lp ni p p0 p1 p2 q0 q1 q2 q3 q4 q5 r sc ss tf tf1 tfa tff 
                tfn zf
               ) 
  (defun getpt (p0 msg tf) 
    (while 
      (and msg 
           (progn (initget 128) 
                  (setq p (&OSNP 
                            p0
                            (strcat "\n点取尺寸断开点(或输断开" 
                                    (if tf "长度)" "角度)")
                                    msg
                                    "<退出>: "
                            )
                          )
                  )
           )
      )
      (cond 
        ((listp p) (setq msg nil))
        ((= (read p) (atof p))
         (setq p (atof p))
         (cond 
           ((equal p 0 mma) (princ "\n**输入值不能为0！"))
           ((and (null tf) (= e70 2) (>= (abs p) 180))
            (princ "\n**AutoCAD 只能处理锐角的角度标注！")
           )
           ((and (null tf) (>= (abs p) 360)) (princ "\n**拆分角度过大，请重现输入。"))
           ('T (setq msg nil))
         )
        )
        ((and (/= msg "") 
              (= (type p) 'STR)
              (wcmatch p "/#,/##,/##")
              (setq p (substr p 2))
              (= (read p) (setq p (atoi p)))
              (> p 1)
         )
         (setq p   (list p)
               msg nil
         )
        )
        (T (princ "\n**输入错误，请重现输入。"))
      )
    )
    p
  )
  (defun pos01 (p) (polar p ay (if (< (distance p q3) (distance p q4)) ds de)))
  (defun pos5 (a) 
    (if (< a as) (setq a (+ a _2pi)))
    (polar q0 a (if (< (abs (- a as)) (abs (- a ae))) ds de))
  )
  (defun pos2 (a / l) 
    (if (< a as) (setq a (+ a _2pi)))
    (setq l (if (< (abs (- a as)) (abs (- a ae))) ds de))
    (list (polar q0 (+ a (cadr l)) (car l)) (polar q0 (+ a (cadddr l)) (caddr l)))
  )
  (defun modent (l / el i ni e70) 
    (setq el (car l)
          el (entget el)
          l  (cdr l)
    )
    (if (> (setq e70 (cdr (assoc 70 el))) 128) 
      (setq l (append l (list 70 (- e70 128))))
    )
    (while l 
      (setq i  (fix (car l))
            ni (cadr l)
            l  (cddr l)
      )
      (if (< 9 i 21) (setq ni (lib::u2wcs ni)))
      (setq el (subst (cons i ni) (assoc i el) el))
    )
    (entmod el)
  )
  (defun update (e1 i1 i2 / l1 l2) 
    (cond 
      (tf (modent (list e1 is (pos01 i1) ie (pos01 i2))))
      ((= e70 2)
       (setq l1 (pos2 i1)
             l2 (pos2 i2)
       )
       (modent 
         (list e1 
               (car is)
               (car l1)
               (cadr is)
               (cadr l1)
               (car ie)
               (car l2)
               (cadr ie)
               (cadr l2)
               16
               (polar q0 (* (+ i1 i2) 0.5) r)
         )
       )
      )
      ((= e70 5)
       (modent 
         (list e1 is (pos5 i1) ie (pos5 i2) 10 (polar q0 (* (+ i1 i2) 0.5) r))
       )
      )
    )
  )
  (defun atstart (/ tf1 p p1 p2) 
    (if tf 
      (setq tf1 (< (distance i i1) (distance i i2)))
      (progn 
        (if 
          (if tfn 
            (setq tf1 (minusp tfn))
            (setq p   (polar q0 i r)
                  p1  (polar q0 i1 r)
                  p2  (polar q0 i2 r)
                  tf1 (< (distance p p1) (distance p p2))
            )
          )
          (progn (if (and (> i1 i2) (< i i1)) (setq i (+ i _2pi))) 
                 (if (and (< i1 i2) (> i i1)) (setq i (- i _2pi)))
          )
          (progn (if (and (> i2 i1) (< i i2)) (setq i (+ i _2pi))) 
                 (if (and (< i2 i1) (> i i2)) (setq i (- i _2pi)))
          )
        )
        (setq as (min i i1 i2))
      )
    )
    tf1
  )
  (defun isPi (a1 a2 a3 tfa) 
    (if tf 
      (setq tfa nil)
      (if (null tfa) 
        (foreach a (if (= e70 2) (list 0 pi _2pi) (list 0 _2pi)) 
          (setq tfa (or tfa (equal (abs (- a1 a2)) a mma)))
          (if a3 (setq tfa (or tfa (equal (abs (- a2 a3)) a mma))))
        )
      )
    )
    tfa
  )
  (defun bzhdk (/ e1 i1 i2 l l1 l2 le1 tff tfa) 
    (setq i1  (car lp)
          lp  (cdr lp)
          tfa nil
    )
    (if lp 
      (progn 
        (setq e1 e
              le nil
        )
        (foreach i2 lp 
          (setq le (cons (list e1 i1 i2) le))
          (update e1 i1 i2)
          (if (not (equal i2 (last lp))) 
            (progn (command ".copy" e1 "" '(0 0 0) "") 
                   (setq e1 (entlast)
                         i1 i2
                   )
            )
          )
        )
      )
      (progn (setq i i1) 
             (if (and (null tf) (< i as)) (setq i (+ i _2pi)))
             (foreach l le 
               (mapcar 'set '(e1 i1 i2) l)
               (if (null tff) 
                 (if 
                   (setq tff (if tf 
                               (equal (+ (distance i1 i) (distance i i2)) 
                                      (distance i1 i2)
                                      mma
                               )
                               (or (> i1 i i2) (< i1 i i2))
                             )
                   )
                   (if (not (setq tfa (isPi i1 i i2 tfa))) 
                     (progn (setq le1 (cons (list e1 i1 i) le1)) 
                            (update e1 i1 i)
                            (command ".copy" e1 "" '(0 0 0) "")
                            (setq e1  (entlast)
                                  le1 (cons (list e1 i i2) le1)
                            )
                            (update e1 i i2)
                     )
                   )
                   (setq le1 (cons l le1))
                 )
                 (setq le1 (cons l le1))
               )
             )
             (if tff 
               (if le1 (setq le (reverse le1)))
               (progn 
                 (setq l1 (car le)
                       l2 (last le)
                       i1 (cadr l1)
                       i2 (caddr l2)
                 )
                 (if (not (setq tfa (isPi i i1 nil tfa))) 
                   (if (atstart) 
                     (progn (command ".copy" (car l1) "" '(0 0 0) "") 
                            (setq e1 (entlast)
                                  le (cons (list e1 i i1) le)
                            )
                            (update e1 i i1)
                     )
                     (progn (command ".copy" (car l2) "" '(0 0 0) "") 
                            (setq e1 (entlast)
                                  le (append le (list (list e1 i2 i)))
                            )
                            (update e1 i2 i)
                     )
                   )
                 )
               )
             )
      )
    )
    tfa
  )
  (lib::LspBeg)
  (setq tf  T
        mx  1e5
        mma 1e-3
  )
  (while 
    (and tf (setq e (&DOVR "\n选取要拆分的尺寸(定位基点靠近点取位置)<退出>: " (dim:flt '(0 1 2 5)))))
    (setq p   (cadr e)
          e   (car e)
          e70 (rem (&DRAG 70) 32)
          q1  (&DRAG 10)
          q3  (&DRAG 13)
          q4  (&DRAG 14)
          tf  nil
    )
    (cond 
      ((< e70 2)
       (setq ax (if (zerop e70) (&DRAG 50) (angle q3 q4))
             sc (&DRAG 3)
       )
       (if (wcmatch sc "*_*_*") 
         (setq sc (&PLCN sc "_")
               sc (/ (atof (caddr sc)) (atof (cadr sc)))
         )
         (setq sc 1)
       )
       (setq p1 (inters q1 (polar q1 ax mx) q3 (polar q3 (+ ax _pi2) mx) nil)
             p2 (inters q1 (polar q1 ax mx) q4 (polar q4 (+ ax _pi2) mx) nil)
             ay (angle p1 q3)
             is 13
             ie 14
             ds (distance p1 q3)
             de (distance p2 q4)
       )
       (if (setq zf (> (distance p p1) (distance p p2))) 
         (progn (&PMLAY "p1" "p2") (&PMLAY "is" "ie"))
       )
       (setq le (list (list e p1 p2))
             ax (angle p1 p2)
       )
      )
      ((member e70 '(2 5))
       (if (= e70 2) 
         (if 
           (setq q2 (&DRAG 15)
                 q5 (&DRAG 16)
                 q0 (inters q1 q2 q3 q4 nil)
           )
           (progn 
             (setq r   (distance q0 q5)
                   ax  (angle q0 q5)
                   ax1 (if 
                         ((if (> (&MIDP q5 q3 q4) 0) > <) 
                           (&MIDP q1 q3 q4)
                           (&MIDP q2 q3 q4)
                         )
                         (angle q2 q1)
                         (angle q1 q2)
                       )
                   ax2 (if 
                         ((if (> (&MIDP q5 q1 q2) 0) > <) 
                           (&MIDP q3 q1 q2)
                           (&MIDP q4 q1 q2)
                         )
                         (angle q4 q3)
                         (angle q3 q4)
                       )
             )
             (if (< ax2 ax1) (setq ax2 (+ ax2 _2pi)))
             (if (< ax ax1) (setq ax (+ ax _2pi)))
             (setq ds (list (distance q0 q1) 
                            (- (angle q0 q1) ax1)
                            (distance q0 q2)
                            (- (angle q0 q2) ax1)
                      )
                   de (list (distance q0 q3) 
                            (- (angle q0 q3) ax2)
                            (distance q0 q4)
                            (- (angle q0 q4) ax2)
                      )
                   is (list 10 15)
                   ie (list 13 14)
             )
             (if (not (> ax2 ax ax1)) 
               (progn (&PMLAY "ax1" "ax2") 
                      (&PMLAY "ds" "de")
                      (&PMLAY "is" "ie")
                      (if (> ax1 _2pi) (setq ax1 (- ax1 _2pi)))
                      (if (< ax2 ax1) (setq ax2 (+ ax2 _2pi)))
               )
             )
           )
           (setq tf (princ "\n**AutoCAD不能处理180°的圆弧，请重现选取！"))
         )
         (progn 
           (setq q0 (&DRAG 15)
                 r  (distance q0 q1)
           )
           (setq ax1 (angle q0 q3)
                 ax2 (angle q0 q4)
                 is  13
                 ie  14
           )
           (if (< (distance q1 q4) (distance q1 q3)) 
             (progn (&PMLAY "q3" "q4") (&PMLAY "ax1" "ax2") (&PMLAY "is" "ie"))
           )
           (if (< ax2 ax1) (setq ax2 (+ ax2 _2pi)))
           (setq ds (distance q0 q3)
                 de (distance q0 q4)
           )
         )
       )
       (if q0 
         (progn 
           (setq p1 (polar q0 ax1 r)
                 p2 (polar q0 ax2 r)
                 sc (/ pi 180.)
                 as ax1
                 ae ax2
           )
           (if (setq zf (> (distance p p1) (distance p p2))) 
             (progn (&PMLAY "p1" "p2") (&PMLAY "ax1" "ax2") (&PMLAY "is" "ie"))
           )
           (setq ax ax1
                 le (list (list e ax1 ax2))
           )
         )
       )
      )
      (T (setq tf (princ "\n**本程序只能处理直线或角度标注，请重新选取!")))
    )
  )
  (if e 
    (progn 
      (setq msg "或 n等分(/n) "
            tf  (< e70 2)
      )
      (lib::Hlt e 3)
      (while (and msg (setq p (getpt p1 msg tf))) 
        (setq msg (if (and (listp p) (null (cadr p))) nil "")
              p0  p1
        )
        (cond 
          ((and (listp p) (null (cadr p)))
           (setq p (car p))
           (if tf 
             (setq dx (/ (distance p1 p2) p)
                   p2 p1
                   lp (list p1)
             )
             (setq dx  (/ (- ax2 ax1) p)
                   ax2 ax1
                   lp  (list ax1)
             )
           )
           (repeat p 
             (if tf 
               (setq p2 (polar p2 ax dx)
                     lp (cons p2 lp)
               )
               (setq ax2 (+ ax2 dx)
                     lp  (cons ax2 lp)
               )
             )
           )
           (setq lp (reverse lp))
          )
          ((atom p)
           (setq dx  (* sc p)
                 tfn p
           )
           (if tf 
             (setq p1 (polar p1 ax dx)
                   lp (list p1)
             )
             (setq ax ((if zf - +) ax dx)
                   p1 (polar q0 ax r)
                   lp (list ax)
             )
           )
          )
          (T
           (setq tfn nil)
           (if tf 
             (setq p1 (inters p (polar p (+ ax _pi2) mx) p1 p2 nil)
                   lp (list p1)
             )
             (setq ax (angle q0 p)
                   p1 (polar q0 ax r)
                   lp (list ax)
             )
           )
          )
        )
        (if (bzhdk) 
          (progn (setq p1 p0) 
                 (if (null tf) (setq ax (angle q0 p1)))
                 (princ "\n**AutoCAD不能处理该角度的标注！")
          )
          (foreach e le (if (list e) (lib::Hlt (car e) 3)))
        )
      )
      (setq ss (ssadd))
      (foreach e le (if (list e) (progn (lib::Hlt (car e) 4) (ssadd (car e) ss))))
      (if (> (sslength ss) 0) (&CODE ss))
    )
  )
  (&TSTY)
)
(defun dim:udtdft (e0 / e st st1) 
  (setq e (cdr (assoc -2 (tblsearch "block" (&DRAG e0 2)))))
  (while e 
    (if (= (&DRAG e 0) "MTEXT") 
      (setq st (last (&PLCN (&DRAG 1) ";"))
            e  nil
      )
      (setq e (entnext e))
    )
  )
  (lib::Hlt e0 3)
  (setq st1 (getstring (strcat "\n输入尺寸标注值<" st ">: ")))
  (lib::Hlt e0 4)
  (if (and (read st1) (/= st st1)) (progn (command ".dim1" "new" st1 e0 "") t))
)
(setfunhelp "c:Xxbzh" "Tssd" "XXBZH")
(defun c:Xxbzh (/ a d e e0 el p1 p10 p13 p14 p2 q13 q14 ss tf tf1 getpts) 
  (Defun getpts (/ msg p1 tf) 
    (setq tf (&GPTS "Tssd/Lsp_Myj/Xxbzh"))
    (while 
      (and (setq msg (strcat "\n点取标注的起点[" (if (= tf "1") "取消" "自动") "对齐(A)]<退出>: ")) 
           (progn (initget "A") (setq p1 (&OSNP msg)))
           (= p1 "A")
      )
      (setq tf (if (= tf "1") "0" "1"))
      (&GLAY "Tssd/Lsp_Myj/Xxbzh" tf)
    )
    (if p1 (cons tf p1))
  )
  (lib::LspBeg)
  (if 
    (and (setq p1 (getpts)) 
         (setq tf1 (= (car p1) "1")
               p1  (cdr p1)
         )
         (setq p2 (&OSNP p1 "\t终点<退出>: "))
    )
    (progn (&LJIG "当前标注" t) 
           (&GVAL)
           (setq e0 (entlast))
           (command ".dimlinear" p1 p2)
           (&SWTO T)
           (princ "\n点取文字标注位置<退出>: ")
           (command pause)
           (setq e  (entlast)
                 ss (ssadd e)
           )
           (if (and e (not (eq e e0))) 
             (progn 
               (if tf1 
                 (progn 
                   (setq p10 (&DRAG e 10)
                         a   (&DRAG 50)
                         p1  (polar p10 a 1e3)
                         p13 (&DRAG 13)
                         q13 (lib::peronl p13 p1 p10)
                         a   (angle p13 q13)
                         p14 (&DRAG 14)
                         q14 (lib::peronl p14 p1 p10)
                         d   (- (distance p13 q13) (distance p14 q14))
                   )
                   (if (minusp d) 
                     (setq p14 (polar p14 a (abs d))
                           el  (list (list 14 (lib::u2wcs p14)))
                     )
                     (setq p13 (polar p13 a (abs d))
                           el  (list (list 13 (lib::u2wcs p13)))
                     )
                   )
                   (lib::eupd e el)
                 )
               )
               (setq tf (dim:udtdft e)
                     p1 p2
               )
               (while (setq p1 (&OSNP p1 "\n点取连续标注位置<结束>: ")) 
                 (command ".dimcontinue" 
                          (if tf1 (lib::peronl p1 p13 p14) p1)
                          ""
                          ""
                 )
                 (setq e (entlast))
                 (if tf (dim:udtdft e))
                 (ssadd e ss)
               )
               (if (> (sslength ss) 1) (&CODE ss))
             )
           )
    )
  )
  (&TSTY)
)
(setfunhelp "c:Dqbzh" "Tssd" "DQBZH")
(defun c:Dqbzh (/ e e0 p1 p2 pn ss tf) 
  (lib::LspBeg)
  (if (and (setq p1 (&OSNP "\n点取标注的起点<退出>: ")) (setq p2 (&OSNP p1 "\t终点<退出>: "))) 
    (progn (&LJIG "当前标注" t) 
           (&GVAL)
           (setq e0 (entlast))
           (command ".dimaligned" p1 p2)
           (&SWTO T)
           (princ "\n点取文字标注位置<退出>: ")
           (command pause)
           (setq e  (entlast)
                 ss (ssadd e)
           )
           (if (and e (not (eq e e0))) 
             (progn 
               (setq tf (dim:udtdft e)
                     pn p2
               )
               (while (setq pn (&OSNP pn "\n点取连续标注位置<结束>: ")) 
                 (command ".dimcontinue" (lib::peronl pn p1 p2) "" "")
                 (setq e (entlast))
                 (if tf (dim:udtdft e))
                 (ssadd e ss)
               )
               (if (> (sslength ss) 1) (&CODE ss))
             )
           )
    )
  )
  (&TSTY)
)
(setfunhelp "c:Pxbzh" "Tssd" "PXBZH")
(defun c:Pxbzh (/ ax ay di dm e l lp lp1 p0 p1 p1x p1y p2 si ss tf) 
  (lib::LspBeg)
  (if 
    (and (setq p1 (&OSNP "\n点取要平行标注的第一点<退出>: ")) 
         (setq p2 (&OSNP p1 "\t第二点<退出>: "))
    )
    (progn (setq lp (list p2 p1)) 
           (while (setq p2 (&OSNP p2 "\t下一点<结束>: ")) (setq lp (cons p2 lp)))
           (setq ax  (car (lib::gpal nil))
                 ay  (- ax _pi2)
                 p1x (polar p1 ax 1e3)
                 p1y (polar p1 ay 1e3)
           )
           (foreach p0 lp 
             (setq di  (&MIDP p0 p1 p1x)
                   lp1 (cons (cons (&MIDP p0 p1 p1y) p0) lp1)
             )
             (if (or (null dm) (< dm di)) 
               (setq dm di
                     p2 p0
               )
             )
           )
           (setq p1  p2
                 p1x (polar p1 ax 1e3)
                 lp  (reverse 
                       (mapcar '(lambda (l) (lib::peronl (cdr l) p1 p1x)) 
                               (lib::ran3 lp1)
                       )
                     )
                 p1  (car lp)
                 ss  (ssadd)
           )
           (&LJIG "当前标注" t)
           (&GVAL)
           (foreach p2 (cdr lp) 
             (setq p0 (polar (&N2S p1 p2) ay (* &sp 8)))
             (ssadd (lib::DimR ax p1 p2 p0 nil) ss)
             (setq p1 p2)
           )
           (&DSTY ss 0)
           (if (> (sslength ss) 1) (&CODE ss))
           (setq si 0)
           (while (setq e (ssname ss si)) 
             (cond ((zerop si) (setq tf (dim:udtdft e))) (tf (dim:udtdft e)))
             (setq si (1+ si))
           )
    )
  )
  (&TSTY)
)
(defun dim:divpal (e q1 q2 / l l1 p3 q3) 
  (if 
    (setq l  lpe
          p3 (inters p1 p2 q1 q2)
    )
    (progn 
      (while 
        (and (setq l1 (car l)) 
             (setq q3 (inters q1 q2 (cadar l1) (caddar l1) nil))
             (< (distance q1 q3) 1e7)
        )
        (setq l (cdr l))
      )
      (setq l   (list e p3 (&N2S (&N2S q1 q2) q1))
            lpe (if l1 (subst (cons l l1) l1 lpe) (cons (list l) lpe))
      )
    )
  )
)
(setfunhelp "c:Zhdbzh" "Tssd" "ZHDBZH")
(defun c:Zhdbzh (/ ax ay d e i l1 l2 l42 lpe p1 p2 q1 q2 si ss) 
  (lib::LspBeg)
  (if 
    (and (setq p1 (&OSNP "\n点取【逐点标注】起始点<退出>：")) 
         (setq p2 (&OSNP p1 "\t结束点<退出>："))
         (setq ss (lib::sslf p1 p2 '((0 . "line,lwpolyline"))))
    )
    (progn 
      (foreach si ss 
        (setq e  (car si)
              q1 (&DRAG e 10)
              q2 (&DRAG 11)
        )
        (if q2 
          (dim:divpal e q1 q2)
          (progn 
            (setq i   1
                  l1  q1
                  l42 (&DRAG 42)
                  q1  (car l1)
                  q2  (last l1)
            )
            (if (and (= (&DRAG 70) 1) (zerop (last l42)) (inters p1 p2 q1 q2)) 
              (dim:divpal e (car l1) (last l1))
            )
            (while (< i (length l1)) 
              (setq q2 (nth i l1))
              (if (and (zerop (nth (1- i) l42)) (inters p1 p2 q1 q2)) 
                (dim:divpal e q1 q2)
              )
              (setq q1 q2
                    i  (1+ i)
              )
            )
          )
        )
      )
      (setq i  0
            si 0
      )
      (foreach l1 lpe 
        (if (> (setq si (length l1)) i) 
          (setq i  si
                l2 l1
          )
        )
      )
      (setq ss nil
            ss (ssadd)
      )
      (foreach l1 l2 (ssadd (car l1) ss))
      (princ "\n选择不需要标注的线<无>: ")
      (setvar "highlight" 1)
      (command "select" ss "r" pause)
      (setq ay  (angle (cadar l2) (caddar l2))
            ax  (- ay _pi2)
            p1  (&N2S p1 p2)
            q1  (polar p1 ay 1e7)
            ss  (ssget "p")
            lpe nil
      )
      (foreach l1 l2 
        (if (ssmemb (car l1) ss) (setq lpe (cons (&MIDP (cadr l1) p1 q1) lpe)))
      )
      (setq lpe (lib::ran1 lpe)
            q1  (polar p1 ax (car lpe))
      )
      (&LJIG "当前标注" t)
      (&GVAL)
      (setq ss (ssadd))
      (foreach d (cdr lpe) 
        (setq q2 (polar p1 ax d))
        (ssadd (lib::DimR ax q1 q2 (&N2S q1 q2) nil) ss)
        (setq q1 q2)
      )
      (&DSTY ss 0)
      (if (> (sslength ss) 1) (&CODE ss))
    )
  )
  (&TSTY)
)
(setfunhelp "c:Lqzhb" "Tssd" "LQZHB")
(defun c:Lqzhb (/ ax ay d d1 d2 e i l1 l2 lpe p1 p2 q1 q2 si ss tf) 
  (lib::LspBeg)
  (if 
    (and (setq p1 (&OSNP "\n点取【中线标注】的起始点<退出>：")) 
         (setq p2 (&OSNP p1 "\t结束点<退出>："))
         (setq ss (lib::sslf 
                    p1
                    p2
                    (list '(0 . "line") 
                          (cons 8 
                                (&LJIG 
                                  "平面主梁,平面主梁实线,平面次梁,平面次梁实线,平面过梁,平面过梁实线,平面连梁,平面连梁实线,平面砼墙,平面砼墙虚线,平面砖墙,平面砖墙虚线"
                                )
                          )
                    )
                  )
         )
    )
    (progn 
      (foreach si ss 
        (setq e  (car si)
              q1 (&DRAG e 10)
              q2 (&DRAG 11)
        )
        (dim:divpal e q1 q2)
      )
      (setq i  0
            si 0
      )
      (foreach l1 lpe 
        (if (> (setq si (length l1)) i) 
          (setq i  si
                l2 l1
          )
        )
      )
      (setq ay  (angle (cadar l2) (caddar l2))
            ax  (- ay _pi2)
            p1  (&N2S p1 p2)
            q1  (polar p1 ay 1e7)
            lpe nil
      )
      (foreach l1 l2 (setq lpe (cons (&MIDP (cadr l1) p1 q1) lpe)))
      (setq lpe (lib::ran1 lpe)
            l1  nil
            l2  nil
            d1  (car lpe)
            tf  t
      )
      (foreach d2 (cdr lpe) 
        (setq d1 (- d2 d1))
        (if tf (setq l1 (cons d1 l1)) (setq l2 (cons d1 l2)))
        (setq tf (not tf)
              d1 d2
        )
      )
      (setq d1 (/ (apply '+ l1) (length l1))
            d2 (/ (apply '+ l2) (length l2))
      )
      (if (< d1 d2) 
        (setq l1 nil)
        (setq l1  (list (car lpe))
              lpe (cdr lpe)
        )
      )
      (while 
        (setq d1 (car lpe)
              d2 (cadr lpe)
        )
        (setq l1  (cons (* 0.5 (+ d1 d2)) l1)
              lpe (cddr lpe)
        )
      )
      (if lpe (setq l1 (append lpe l1)))
      (setq lpe (reverse l1)
            d1  (car lpe)
            q1  (polar p1 ax d1)
            ss  (ssadd)
      )
      (&LJIG "当前标注" t)
      (&GVAL)
      (foreach d (cdr lpe) 
        (setq q2 (polar p1 ax d))
        (ssadd (lib::DimR ax q1 q2 (&N2S q1 q2) nil) ss)
        (setq q1 q2)
      )
      (&DSTY ss 0)
    )
  )
  (&TSTY)
)
(setfunhelp "c:Lkqh" "Tssd" "LKQH")
(defun dim:LkQh (tf / a1 a2 ax ay d0 d1 d2 e l1 l2 l3 ll lae lpe p p1 p2 q1 q2 r r1 
                 si ss wid
                ) 
  (lib::LspBeg)
  (if 
    (and (setq p1 (&OSNP (strcat "\n点取【" (if tf "宽度标注" "偏心定位") "】的起始点<退出>："))) 
         (setq p2 (&OSNP p1 "\t结束点<退出>："))
         (setq ss (lib::sslf 
                    p1
                    p2
                    (list '(0 . "line,arc") 
                          (cons 8 
                                (&LJIG 
                                  "平面主梁,平面主梁实线,平面次梁,平面次梁实线,平面过梁,平面过梁实线,平面连梁,平面连梁实线,平面砼墙,平面砼墙虚线,平面砖墙,平面砖墙虚线,平面轴线"
                                )
                          )
                    )
                  )
         )
    )
    (progn 
      (foreach si ss 
        (setq e (car si))
        (if (= (&DRAG e 0) "LINE") 
          (progn 
            (setq q1 (&DRAG 10)
                  q2 (&DRAG 11)
            )
            (dim:divpal e q1 q2)
          )
          (progn 
            (setq q1 (&DRAG 10)
                  r  (&DRAG 40)
                  a1 (&DRAG 50)
                  a2 (&DRAG 51)
            )
            (foreach p (&ORDR p1 p2 q1 r a1 a2) 
              (setq lae (cons (list (atof (rtos (distance p1 p) 2 2)) q1 r p) lae))
            )
          )
        )
      )
      (setq wid (* &sc 1200)
            ss  (ssadd)
      )
      (&LJIG "当前标注" t)
      (&GVAL)
      (foreach l2 lpe 
        (setq ay (angle (cadar l2) (caddar l2))
              ax (- ay _pi2)
              p1 (cadar l2)
              q1 (polar p1 ay 1e7)
              l3 nil
        )
        (foreach l1 l2 
          (setq l3 (cons (atof (rtos (&MIDP (cadr l1) p1 q1) 2 2)) l3))
        )
        (setq l3 (lib::ran1 l3)
              d1 (car l3)
              q1 (polar p1 ax d1)
              ll nil
        )
        (foreach d2 (cdr l3) 
          (setq q2 (polar p1 ax d2))
          (cond 
            ((and (< (setq d0 (- d2 d1)) wid) 
                  (or tf 
                      (null ll)
                      (and (not (equal (car ll) d0 1e-3)) 
                           (equal (last ll) q1 1e-3)
                      )
                  )
             )
             (ssadd (lib::DimR ax q1 q2 q1 nil) ss)
             (if (null tf) (setq ll (list d0 (entlast) q2)))
            )
            ((and ll (equal (car ll) d0 1e-3) (equal (last ll) q1 1e-3))
             (ssdel (cadr ll) ss)
             (entdel (cadr ll))
             (setq ll nil)
            )
            (t (setq ll nil))
          )
          (setq q1 q2
                d1 d2
          )
        )
      )
      (if lae 
        (progn 
          (setq lae (mapcar 'cdr (lib::ran3 lae))
                p1  (caar lae)
                r   (cadar lae)
                p2  (caddar lae)
                a1  (angle p1 p2)
                ll  nil
          )
          (foreach l2 (cdr lae) 
            (setq q1 (car l2)
                  r1 (cadr l2)
                  q2 (caddr l2)
            )
            (cond 
              ((and (equal p1 q1 10) 
                    (not (equal r r1 10))
                    (< (setq d0 (abs (- r r1))) wid)
                    (setq q2 (polar q1 a1 r1))
                    (or tf 
                        (null ll)
                        (and (not (equal (car ll) d0 1e-3)) 
                             (equal (last ll) p2 1e-3)
                        )
                    )
               )
               (ssadd (lib::DimR a1 p2 q2 p2 nil) ss)
               (if (null tf) (setq ll (list d0 (entlast) q2)))
              )
              ((and ll (equal (car ll) d0 1e-3) (equal (last ll) p2 1e-3))
               (ssdel (cadr ll) ss)
               (entdel (cadr ll))
               (setq ll nil)
              )
              (t (setq ll nil))
            )
            (setq p1 q1
                  r  r1
                  p2 q2
                  a1 (angle p1 p2)
            )
          )
        )
      )
      (if (> (sslength ss) 1) (&CODE ss) (princ "\n**没有符合标注的梁、墙！"))
    )
  )
  (&TSTY)
)
(setfunhelp "c:Lkqh" "Tssd" "LKQH")
(defun c:Lkqh () (dim:LkQh T))
(setfunhelp "c:PxDw" "Tssd" "PxDw")
(defun c:PxDw () (dim:LkQh nil))
(setfunhelp "c:Chdchl" "Tssd" "CHDCHL")
(defun c:Chdchl (/ ss) 
  (lib::LspBeg)
  (if (setq ss (&DSTR "\n选择要进行重叠处理的尺寸<退出>: " '((0 . "dimension")))) (&CODE ss))
  (&TSTY)
)
(setfunhelp "c:Chcbwz" "Tssd" "CHCBWZ")
(defun c:Chcbwz (/ e e0 lay si ss) 
  (lib::LspBeg)
  (if (setq ss (&DSTR "\n选择要变为文字的尺寸线<退出>: " '((0 . "dimension")))) 
    (progn 
      (setq e0  (entlast)
            lay (list (list 8 (&LJIG "当前文字" t)))
            si  -1
      )
      (while 
        (setq si (1+ si)
              e  (ssname ss si)
        )
        (command ".explode" e)
      )
      (setq e e0)
      (while (setq e (entnext e)) 
        (if (wcmatch (&DRAG e 0) "*TEXT") (lib::eupd e lay) (entdel e))
      )
    )
  )
  (&TSTY)
)
(setfunhelp "c:gjbzhfw" "Tssd" "gjbzhfw")
(defun c:gjbzhfw (/ ay e0 e1 l lay le p0 p1 p2 pt1 pt2 px x ecolor getrein *error*) 
  (Defun ecolor (le co / e l x) 
    (setq co (list (list 62 co)))
    (foreach e le (foreach l (lib::GetGrps e) (foreach x l (lib::eupd x co))))
    nil
  )
  (Defun getrein (pt1 pt2 / e flt l le lp p0 si ss) 
    (setq flt (list (cons 8 (&LJIG "平面楼板正筋钢筋,平面楼板负筋钢筋")) '(0 . "lwpolyline")))
    (if (setq ss (ssget "f" (list pt1 pt2) flt)) 
      (progn (setq si -1) 
             (while 
               (setq si (1+ si)
                     e  (ssname ss si)
               )
               (setq le (cons e le))
             )
             (ecolor le 6)
             (cond 
               ((null (setq e (&DOVR "\n选取要保留的钢筋,其他均被删除<退出>: "))) (setq l nil))
               ((not (member (car e) le)) (setq l (prompt "\n**选取的钢筋未在标注范围内！")))
               (t
                (setq p0 (osnap (cadr e) "nea")
                      lp (lib::whpl 
                           (lib::pl2l (&DRAG 10) (&DRAG 70) (&DRAG 42))
                           p0
                         )
                      l  (list p0 (car lp) (cadr lp) (car e))
                )
               )
             )
             (if l (append l le) (ecolor le 256))
      )
      (prompt "\n**未发现需要标注的钢筋！")
    )
  )
  (Defun *error* (msg) (if le (ecolor le 256)) (*merr* msg))
  (lib::LspBeg)
  (if 
    (and (setq pt1 (&OSNP "\n点取标注起点位置<退出>: ")) 
         (setq pt2 (&OSNP pt1 "\t终点<退出>: "))
         (setq le (getrein pt1 pt2))
    )
    (progn (&GVAL) 
           (&LJIG "当前标注" t)
           (setq e0  (entlast)
                 p0  (car le)
                 p1  (cadr le)
                 p2  (caddr le)
                 le  (cdddr le)
                 ay  (+ (angle p1 p2) _pi2)
                 px  (polar p0 ay &sp)
                 pt1 (lib::peronl pt1 p0 px)
                 pt2 (lib::peronl pt2 p0 px)
           )
           (prompt "\t标注位置<退出>: ")
           (command ".Dimaligned" pt1 pt2 "T" " " pause)
           (setq e1 (entlast))
           (ecolor (cdr le) 256)
           (cond 
             ((eq e0 e1) nil)
             ((null 
                (setq p0  (&DRAG e1 11)
                      px  (polar p0 ay &sp)
                      pt1 (lib::peronl pt1 p0 px)
                      pt2 (lib::peronl pt2 p0 px)
                      p0  (inters pt1 pt2 p1 p2)
                )
              )
              (prompt "\n**标注点在钢筋外，无法标注!")
              (entdel e1)
             )
             (t
              (command ".Circle" p0 &sp)
              (setq e0  (car le)
                    lay (strcase (&DRAG e0 8))
              )
              (foreach e1 (cdr le) 
                (cond 
                  ((eq e0 e1) nil)
                  ((= (strcase (&DRAG e1 8)) lay)
                   (foreach l (lib::GetGrps e1) (foreach x l (entdel x)))
                  )
                )
              )
             )
           )
    )
  )
  (&TSTY)
)
(setfunhelp "c:Chcjch" "Tssd" "Chcjch")
(defun c:Chcjch (/ ang e en h p1 p2 p3 p4 pt ss str w) 
  (lib::LspBeg)
  (if (setq ss (&DSTR "\n选择要检查原值的尺寸<退出>: " '((0 . "dimension")))) 
    (progn (command ".Layer" "M" "Tsz_Dim_Temp" "C" "1" "" "") 
           (while (setq en (ssname ss 0)) 
             (ssdel en ss)
             (setq str (&DRAG en 1))
             (if (and (/= str "") (/= str "<>")) 
               (progn (setq e (cdr (assoc -2 (tblsearch "block" (&DRAG en 2))))) 
                      (while e 
                        (if (= (&DRAG e 0) "MTEXT") 
                          (setq pt  (&DRAG 10)
                                ang (&DRAG 50)
                                h   (&DRAG 40)
                                w   (&DRAG 42)
                                e   nil
                                p1  (polar (polar pt ang (* 0.6 w)) 
                                           (+ ang (* 0.5 pi))
                                           (* 0.6 h)
                                    )
                                p2  (polar p1 (- ang (* 0.5 pi)) (* 1.2 h))
                                p3  (polar p2 (+ ang pi) (* 1.2 w))
                                p4  (polar p1 (+ ang pi) (* 1.2 w))
                          )
                          (setq e (entnext e))
                        )
                      )
                      (lib::pline (list p1 p2 p3 p4) '((70 . 1)))
               )
             )
           )
    )
  )
  (&TSTY)
)
(setfunhelp "c:shjck" "Tssd" "shjck")
(defun C:shjck (/ ss) 
  (lib::LspBeg)
  (if (setq ss (ssget "x" (list (cons 8 "Tsz_Dim_Temp")))) (ss::del ss))
  (&TSTY)
)
(setfunhelp "c:hjzhh" "Tssd" "hjzhh")
(defun c:hjzhh (/ a a1 a2 e p1 p2 pc si ss str) 
  (lib::LspBeg)
  (if (setq ss (&DSTR "\n选择要进行(角度/弧长)互换的尺寸<退出>: " (dim:flt '(5)))) 
    (progn (setq si -1) 
           (while 
             (setq si (1+ si)
                   e  (ssname ss si)
             )
             (setq str (&DRAG e 1)
                   pc  (&DRAG 15)
                   p1  (&DRAG 13)
                   p2  (&DRAG 14)
                   a1  (angle pc p1)
                   a2  (angle pc p2)
                   a   (- a2 a1)
             )
             (if (< a 0) (setq a (+ a _2pi)))
             (if (or (= str "") (= str "<>")) 
               (setq str (rtos (/ (* (distance pc p1) a) &sc) 2 0))
               (setq str "")
             )
             (lib::eupd e (list (list 1 str)))
           )
    )
  )
  (&TSTY)
)
(setfunhelp "c:ccpb" "Tssd" "ccpb")
(defun c:ccpb (/ _dis a d0 d1 d2 dis e l l1 l2 le p0 px si ss tf) 
  (lib::LspBeg)
  (setq tf   t
        _dis (&GPTS "Tssd/Default_Myj/ccpb_Dis" "8.0")
  )
  (while 
    (and tf 
         (setq ss (&DSTR 
                    (strcat "\n当前的尺寸排版间距为: " _dis "。\n选择要排版的尺寸或 [调整间距(D)]<退出>: ")
                    "Dis"
                    (dim:flt '(0 1))
                  )
         )
    )
    (cond 
      ((= ss "Dis")
       (initget 6)
       (setq dis  (getreal (strcat "\n输入新的排版间距<" _dis ">: "))
             dis  (if dis dis (atof _dis))
             _dis (rtos dis 2 2)
       )
       (&GLAY "Tssd/Default_Myj/ccpb_Dis" _dis)
      )
      (t (setq tf (null ss)))
    )
  )
  (if ss 
    (progn 
      (setq dis (* (atof _dis) &sp)
            si  -1
      )
      (while 
        (setq si (1+ si)
              e  (ssname ss si)
        )
        (setq a  (if (zerop (rem (&DRAG e 70) 32)) 
                   (&DRAG 50)
                   (angle (&DRAG 13) (&DRAG 14))
                 )
              p0 (&DRAG 10)
              px (polar p0 a 1e3)
              a  (atoi (angtos a 0 0))
              a  (lib::atidy a 180)
        )
        (if (setq l (assoc a le)) 
          (progn (setq _dis (atof (rtos (&MIDP p0 (cadr l) (caddr l)) 2 2))) 
                 (if (setq l1 (assoc _dis (cdddr l))) 
                   (setq l2 (subst (append l1 (list (list p0 e))) l1 l))
                   (setq l2 (append l (list (list _dis (list p0 e)))))
                 )
                 (setq le (subst l2 l le))
          )
          (setq le (cons (list a p0 px (list 0.0 (list p0 e))) le))
        )
      )
      (foreach l le 
        (setq p0 (cadr l)
              px (caddr l)
              a  (+ (angle p0 px) _pi2)
              l  (lib::ran4 (cdddr l))
              d1 (caar l)
              d0 d1
              si 0
        )
        (foreach l1 (cdr l) 
          (setq d2 (car l1))
          (if (> (setq _dis (- d2 d1)) (* 0.35 dis)) 
            (setq si (1+ si)
                  d1 d2
            )
          )
          (setq _dis (- d2 d0 (* si dis)))
          (foreach l2 (cdr l1) 
            (setq p0 (polar (car l2) a _dis)
                  e  (cadr l2)
            )
            (lib::eupd e (list (list 10 (lib::u2wcs p0))))
          )
        )
      )
      (if (> si 0) (&CODE ss))
    )
  )
  (&TSTY)
)
(defun dim:axpt (pc r a1 a2 / l la la1 p1 p2 yn) 
  (setq la (list a1 a2))
  (foreach l (lib::ssaf pc r a1 a2 (list '(0 . "line") (cons 8 (&LJIG "平面轴线")))) 
    (setq p1 (&DRAG (car l) 10)
          p2 (&DRAG 11)
    )
    (if (equal (&MIDP pc p1 p2) 0 &sc) 
      (setq a2  (lib::upang (angle pc (&N2S p1 p2)) a1)
            la1 (cons a2 la1)
      )
    )
  )
  (if la1 
    (progn (initget "Yes No") 
           (setq yn (getkword "\n是否标注相关轴线 [是(Y)/否(N)]<否>: "))
           (if (= yn "Yes") (setq la (lib::ran1 (append la la1))))
    )
  )
  la
)
(setfunhelp "c:Jdbzh" "Tssd" "JDBZH")
(defun c:Jdbzh (/ a1 a2 e1 e2 en la p1 p2 pc pt q1 q2 r) 
  (lib::LspBeg)
  (setq e1 (&DOVR "\n选取要标注角度的圆弧、圆、直线<指定顶点>: " '((0 . "arc,circle,line"))))
  (cond 
    ((null e1)
     (if 
       (and (setq pc (&OSNP "\n选取角的顶点<退出>: ")) 
            (setq p1 (&OSNP pc "\n选取角的第一个端点<退出>: "))
            (progn (grdraw pc p1 3 1) T)
            (setq p2 (&OSNP pc "\t另一端点<退出>: "))
       )
       (setq a1 (angle pc p1)
             a2 (angle pc p2)
             r  (distance pc p1)
       )
     )
    )
    ((= "LINE" (setq en (&DRAG 0)))
     (lib::Hlt (car e1) 3)
     (if (setq e2 (&DOVR "\n选取第二条直线<退出>: " '((0 . "line")))) 
       (if 
         (not 
           (and 
             (setq p1 (&DRAG (car e1) 10)
                   p2 (&DRAG 11)
                   q1 (&DRAG (car e2) 10)
                   q2 (&DRAG 11)
                   pc (inters p1 p2 q1 q2 nil)
             )
             (< (distance pc p1) (* 5 (+ (distance p1 p2) (distance q1 q2))))
           )
         )
         (setq pc (prompt "\n**无法标注两根平行直线！"))
       )
     )
     (lib::Hlt (car e1) 4)
    )
    ((= "CIRCLE" en)
     (setq p1 (&DRAG 10))
     (grdraw p1 (cadr e1) 3 1)
     (if (setq p2 (&OSNP p1 "\n选取角的第二个端点<退出>: ")) 
       (setq pc (&DRAG (car e1) 10)
             r  (&DRAG 40)
             a1 (angle pc (cadr e1))
             a2 (angle pc p2)
       )
     )
    )
    ((= "ARC" en)
     (setq e1 (car e1)
           pc (&DRAG 10)
           r  (&DRAG 40)
           a1 (&DRAG 50)
           a2 (&DRAG 51)
     )
    )
  )
  (redraw)
  (if pc 
    (progn (&LJIG "当前标注" t) 
           (&GVAL t)
           (prompt "\n点取标注位置<退出>: ")
           (if e2 
             (command ".dimangular" e1 e2 pause)
             (progn 
               (setq a2 (lib::upang a2 a1)
                     la (dim:axpt pc r a1 a2)
                     a1 (car la)
               )
               (foreach a2 (cdr la) 
                 (if (> (- a2 a1) 0.02) 
                   (progn 
                     (setq p1 (polar pc a1 r)
                           p2 (polar pc a2 r)
                     )
                     (if pt 
                       (setq pt (polar pc (* 0.5 (+ a1 a2)) (distance pc pt)))
                     )
                     (command ".dimangular" "" pc p1 p2)
                     (if pt 
                       (command pt)
                       (progn (command pause) (setq pt (&DRAG (entlast) 10)))
                     )
                   )
                 )
                 (setq a1 a2)
               )
             )
           )
    )
  )
  (&TSTY)
)
(setfunhelp "c:Hchbzh" "Tssd" "HCHBZH")
(defun c:Hchbzh (/ a1 a2 e la p0 p1 p2 pc pt r) 
  (lib::LspBeg)
  (if (setq e (&DOVR "\n选取要标注弧长的圆弧或圆<退出>: " '((0 . "arc,circle")))) 
    (progn 
      (setq p0 (cadr e)
            pc (&DRAG 10)
            r  (&DRAG 40)
      )
      (if (= "ARC" (strcase (&DRAG 0))) 
        (setq a1 (&DRAG 50)
              a2 (&DRAG 51)
        )
        (progn (grdraw p0 pc 3 1) 
               (if (setq p2 (&OSNP (&DRAG (car e) 10) "\n选取角的第二个端点<退出>: ")) 
                 (setq a1 (angle pc p0)
                       a2 (angle pc p2)
                 )
               )
               (redraw)
        )
      )
      (if (and a1 a2) 
        (progn (&LJIG "当前标注" t) 
               (&GVAL t)
               (setq a2 (lib::upang a2 a1)
                     la (dim:axpt pc r a1 a2)
                     a1 (car la)
               )
               (prompt "\n点取标注位置<退出>: ")
               (foreach a2 (cdr la) 
                 (if (> (- a2 a1) 0.02) 
                   (progn 
                     (setq p1 (polar pc a1 r)
                           p2 (polar pc a2 r)
                     )
                     (if pt 
                       (setq pt (polar pc (* 0.5 (+ a1 a2)) (distance pc pt)))
                     )
                     (command ".dimangular" 
                              ""
                              pc
                              p1
                              p2
                              "t"
                              (rtos (/ (* r (- a2 a1)) &sc) 2 0)
                     )
                     (if pt 
                       (command pt)
                       (progn (command pause) (setq pt (&DRAG (entlast) 10)))
                     )
                   )
                 )
                 (setq a1 a2)
               )
        )
      )
    )
  )
  (&TSTY)
)
(Defun dimrd- (sty / dimt e) 
  (lib::LspBeg)
  (setq dimt (getvar "dimfit"))
  (&LJIG "当前标注" t)
  (&GVAL t)
  (setvar "dimdec" 0)
  (setvar "dimfit" 3)
  (setvar "dimtix" 0)
  (setvar "dimtofl" 0)
  (prompt (strcat "\n选取要标注" sty "的圆弧或圆<退出>: "))
  (command (if (= sty "半径") ".dimradius" ".Dimdiameter"))
  (setvar "cmdecho" 1)
  (while (/= (getvar "cmdactive") 0) (command pause))
  (setvar "cmdecho" 0)
  (setvar "dimfit" dimt)
  (&TSTY)
)
(setfunhelp "c:Bjbzh" "Tssd" "BJBZH")
(defun c:Bjbzh () (dimrd- "半径"))
(setfunhelp "c:Zhjbzh" "Tssd" "ZHJBZH")
(defun c:Zhjbzh () (dimrd- "直径"))
